module demomodule {
    namespace "urn:de:fraunhofer:fkie:demomodule";

    prefix dm;

    contact
        "Editor: Henning Rogge <mailto:henning.rogge@fkie.fraunhofer.de>";

    description "Standalone demo for debugging enum list request";

    revision "2023-07-31" {
        description "Demo for debugging";
    }

    container democontainer {
        list demolist {
            key "name";

            leaf name {
                // type string;
                type enumeration {
                    enum MAX_BITRATE_RX;
                    enum MAX_BITRATE_TX;
                }
            }
            leaf value {
                type decimal64;
            }
        }
    }
}
